module golf {
  yang-version "1.1";
  namespace "urn:submodule:golf";
  prefix g;

  include golf-sub;

  container golf {
    container main {
      leaf name {
        type string;
      }
    }

    container from-submodule {
      uses sub-stuff;
    }

    container local {
      leaf name {
        type union {
          type leafref {
            path "../../main/name";
          }
          type enumeration {
            enum none;
          }
        }
      }
    }
  }
}
