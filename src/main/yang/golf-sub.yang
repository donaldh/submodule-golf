submodule golf-sub {
  yang-version "1.1";
  belongs-to golf {
    prefix "g";
  }

  grouping sub-stuff {

    leaf this-works {
      type leafref {
        path "../../main/name";
      }
    }

    leaf broken {
      type union {
        type leafref {
          path "../../main/name";
        }
      }
    }
  }
}
